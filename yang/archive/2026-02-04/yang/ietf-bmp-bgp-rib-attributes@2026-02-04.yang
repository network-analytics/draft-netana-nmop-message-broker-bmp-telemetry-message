submodule ietf-bmp-bgp-rib-attributes {
  yang-version 1.1;
  belongs-to ietf-bmp-telemetry-message {
    prefix bmptm;
  }

  // import some basic types
  import iana-bgp-types {
    prefix bt;
    reference
      "RFC XXXX: YANG Model for Border Gateway Protocol (BGP-4).";
  }
  import iana-bgp-community-types {
    prefix bct;
    reference
      "RFC XXXX: YANG Model for Border Gateway Protocol (BGP-4).";
  }
  import ietf-inet-types {
    prefix inet;
    reference
      "RFC 6991: Common YANG Data Types.";
  }
  import ietf-yang-types {
    prefix yang;
    reference
      "RFC 6991: Common YANG Types.";
  }

  // meta
  organization
    "IETF Draft";
  contact
    "Author:    Thomas Graf
                <mailto:thomas.graf@swisscom.com>
                Paolo Lucente
                <mailto:paolo@ntt.net>
                Leonardo Rodoni
                <mailto:leonardo.rodoni@swisscom.com>";

  description
    "This submodule contains common data definitions for BGP
     attributes for use in BGP RIB tables.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-02-04 {
    description
      "Initial version";
    reference
      "RFC XXXX";
  }

  grouping bgp-common-route-attributes {
    description
      "BGP path attributes and communities.";
    uses bgp-path-attributes;
    uses bgp-community-attr-state;
    uses ext-community-attributes;
    uses ipv6-ext-community-attributes;
    uses large-community-attributes;
  }

  grouping bgp-path-attributes {
    description
      "A grouping for all BGP Path Attribute parameters.";

    container attributes {
      description
        "A container for attribute parameters.";
      leaf origin {
        type bt:bgp-origin-attr-type;
        description
          "BGP attribute defining the origin of the path
           information.";
        reference
          "RFC 4271: A Border Gateway Protocol 4 (BGP-4), Section
           5.1.1.";
      }
      container as-path {
        description
          "Enclosing container for the list of AS path segments.

           In the Adj-RIB-In or Adj-RIB-Out, this list should show
           the received or sent AS_PATH, respectively.  For
           example, if the local router is not 4-byte capable, this
           value should consist of 2-octet ASNs or the AS_TRANS
           (AS 23456) values received or sent in BGP updates.

           In the Loc-RIB, this list should reflect the effective
           AS path for the route, e.g., a 4-octet value if the
           local router is 4-octet capable.";
        reference
          "RFC 4271: A Border Gateway Protocol 4 (BGP-4),
           RFC 6793: BGP Support for Four-octet AS Number Space
           RFC 5065: Autonomous System Confederations for BGP.";
        list segment {
          config false;
          uses bgp-as-path-segment;
          description
            "List of AS PATH segments";
        }
      }
      leaf next-hop {
        type inet:ip-address;
        description
          "BGP next hop attribute defining the IP address of the
           router that should be used as the next hop to the
           destination.  Used when the BGP routes' nexthop for that
           AFI/SAFI can be represented as an IPv4/IPv6 address.";
        reference
          "RFC 4271: A Border Gateway Protocol 4 (BGP-4), Section
           5.1.3.";
      }
      leaf link-local-next-hop {
        type inet:ipv6-address;
        description
          "When both a global and a link-local next-hop are sent
           when following RFC 2545 procedures, this leaf contains
           the link-local next-hop.";
        reference
          "RFC 2545: Use of BGP-4 Multiprotocol Extensions for IPv6
           Inter-Domain Routing.";
      }
      leaf med {
        type uint32;
        description
          "BGP multi-exit discriminator attribute used in the BGP
           route selection process.";
        reference
          "RFC 4271: A Border Gateway Protocol 4 (BGP-4), Section
           5.1.4.";
      }
      leaf local-pref {
        type uint32;
        description
          "BGP local preference attribute sent to internal peers to
           indicate the degree of preference for externally learned
           routes.  The route with the highest local preference
           value is preferred.";
        reference
          "RFC 4271: A Border Gateway Protocol 4 (BGP-4), Section
           5.1.5.";
      }
      container as4-path {
        description
          "This is the path encoded with 4-octet
           AS numbers in the optional transitive AS4_PATH attribute.
           This value is populated with the received or sent
           attribute in Adj-RIB-In or Adj-RIB-Out, respectively.
           It should not be populated in Loc-RIB since the Loc-RIB
           is expected to store the effective AS-Path in the
           as-path leaf regardless of being 4-octet or 2-octet.";
        reference
          "RFC 6793: BGP Support for Four-octet AS Number Space";
        list segment {
          config false;
          uses bgp-as-path-segment;
          description
            "List of AS PATH segments";
        }
      }
      container aggregator {
        config false;
        description
          "BGP attribute indicating the prefix has been
           aggregated by the specified AS and router.";
        reference
          "RFC 4271: A Border Gateway Protocol 4 (BGP-4), Section
           5.1.7,
           RFC 6793: BGP Support for Four-octet AS Number Space.";
        leaf as {
          type inet:as-number;
          description
            "AS number of the autonomous system that performed the
             aggregation.";
          reference
            "RFC 4271: A Border Gateway Protocol 4 (BGP-4), Section
             4.3, Path Attributes (g).";
        }
        leaf identifier {
          type yang:dotted-quad;
          description
            "BGP Identifier of the router that performed the
             aggregation.";
          reference
            "RFC 4271: A Border Gateway Protocol 4 (BGP-4), Section
             4.3, Path Attributes (g).";
        }
      }
      container aggregator4 {
        config false;
        description
          "BGP attribute indicating the prefix has been
           aggregated by the specified AS and router.
           This value is populated with the received or sent
           attribute in Adj-RIB-In or Adj-RIB-Out, respectively.
           It should not be populated in Loc-RIB since the Loc-RIB
           is expected to store the effective AGGREGATOR in the
           aggregator/as leaf regardless of being 4-octet or
           2-octet.";
        reference
          "RFC 6793: BGP Support for Four-octet AS Number Space.";
        leaf as4 {
          type inet:as-number;
          description
            "AS number of the autonomous system that performed the
             aggregation (4-octet representation).  This value is
             populated if an upstream router is not 4-octet capable.
             Its semantics are similar to the AS4_PATH optional
             transitive attribute";
          reference
            "RFC 6793: BGP Support for Four-octet AS Number Space,
             Section 3,
             RFC 4271: A Border Gateway Protocol 4 (BGP-4), Section
             4.3, Path Attributes (g).";
        }
        leaf identifier {
          type yang:dotted-quad;
          description
            "BGP Identifier of the router that performed the
             aggregation.";
          reference
            "RFC 6793: BGP Support for Four-octet AS Number Space,
             Section 3,
             RFC 4271: A Border Gateway Protocol 4 (BGP-4), Section
             4.3, Path Attributes (g).";
        }
      }
      leaf atomic-aggregate {
        type boolean;
        description
          "BGP attribute indicating that the prefix is an atomic
           aggregate; i.e., the peer selected is a less specific
           route without selecting a more specific route that is
           subsumed by it.";
        reference
          "RFC 4271: A Border Gateway Protocol 4 (BGP-4), Section
           5.1.6.";
      }
      leaf originator-id {
        type yang:dotted-quad;
        description
          "BGP attribute that provides the id as an IPv4 address
           of the originator of the announcement.";
        reference
          "RFC 4456: BGP Route Reflection: An Alternative to Full
           Mesh Internal BGP (IBGP).";
      }
      leaf-list cluster-list {
        type yang:dotted-quad;
        description
          "Represents the reflection path that the route has
           passed.";
        reference
          "RFC 4456: BGP Route Reflection: An Alternative to Full
           Mesh Internal BGP (IBGP).";
      }
      leaf aigp-metric {
        type uint64;
        description
          "BGP path attribute representing the accumulated IGP
           metric for the path";
        reference
          "RFC 7311: The Accumulated IGP Metric Attribute for BGP.";
      }
    }
  }

  grouping bgp-as-path-segment {
    description
      "Data for representing BGP AS-PATH segment";

    leaf type {
      type identityref {
        base bt:as-path-segment-type;
      }
      description
        "The type of AS-PATH segment";
    }
    leaf-list member {
      type inet:as-number;
      description
        "List of the AS numbers in the AS-PATH segment";
    }
  }

  grouping bgp-unknown-attr-top {
    description
      "Unknown path attributes that are not expected to be shared
       across route entries, common to LOC-RIB and Adj-RIB";
    container unknown-attributes {
      description
        "Unknown path attributes that were received in the UPDATE
         message which contained the prefix.";

      list unknown-attribute {
        key "attr-type";
        description
          "This list contains received attributes that are
           unrecognized or unsupported by the local router. The list
           may be empty.";

        leaf optional {
          type boolean;
          description
            "Defines whether the attribute is optional (if
             set to true) or well-known (if set to false).
             Set in the high-order bit of the BGP attribute
             flags octet.";
          reference
            "RFC 4271: A Border Gateway Protocol 4 (BGP-4).";
        }

        leaf transitive {
          type boolean;
          description
            "Defines whether an optional attribute is transitive
             (if set to true) or non-transitive (if set to false).
             For well-known attributes, the transitive flag must be
             set to true. Set in the second high-order bit of the BGP
             attribute flags octet.";
          reference
            "RFC 4271: A Border Gateway Protocol 4 (BGP-4).";
        }

        leaf partial {
          type boolean;
          description
            "Defines whether the information contained in the
             optional transitive attribute is partial (if set to
             true) or complete (if set to false). For well-known
             attributes and for optional non-transitive attributes,
             the partial flag must be set to false. Set in the third
             high-order bit of the BGP attribute flags octet.";
          reference
            "RFC 4271: A Border Gateway Protocol 4 (BGP-4).";
        }

        leaf extended {
          type boolean;
          description
            "Defines whether the attribute length is one octet
             (if set to false) or two octets (if set to true). Set in
             the fourth high-order bit of the BGP attribute flags
             octet.";
          reference
            "RFC 4271: A Border Gateway Protocol 4 (BGP-4).";
        }

        leaf attr-type {
          type uint8;
          description
            "1-octet value encoding the attribute type code";
          reference
            "RFC 4271: A Border Gateway Protocol 4 (BGP-4).";
        }

        leaf attr-len {
          type uint16;
          description
            "One or two octet attribute length field indicating the
             length of the attribute data in octets.  If the Extended
             Length attribute flag is set, the length field is 2
             octets, otherwise it is 1 octet";
          reference
            "RFC 4271: A Border Gateway Protocol 4 (BGP-4).";
        }

        leaf attr-value {
          type binary {
            length "0..65535";
          }
          description
            "Raw attribute value, not including the attribute
             flags, type, or length.  The maximum length
             of the attribute value data is 2^16-1 per the max value
             of the attr-len field (2 octets).";
          reference
            "RFC 4271: A Border Gateway Protocol 4 (BGP-4).";
        }
      }
    }
  }

  grouping bgp-adj-rib-attr-state {
    description
      "Path attributes that are not expected to be shared across
       route entries, specific to Adj-RIB";
    leaf path-id {
      type uint32;
      description
        "When the BGP speaker supports advertisement of multiple
         paths for a prefix, the path identifier is used to
         uniquely identify a route based on the combination of the
         prefix and path id.  In the Adj-RIB-In, the path-id value is
         the value received in the update message.   In the Loc-RIB,
         if used, it should represent a locally generated path-id
         value for the corresponding route.  In Adj-RIB-Out, it
         should be the value sent to a neighbor when add-paths is
         used, i.e., the capability has been negotiated.";
      reference
        "RFC 7911: Advertisement of Multiple Paths in BGP.";
    }
  }

  grouping bgp-community-attr-state {
    description
      "Common definition of BGP community attributes";
    leaf-list communities {
      type union {
        type bct:bgp-well-known-community-type;
        type bct:bgp-std-community-type;
      }
      description
        "List of standard or well-known BGP community
         attributes.";
    }
  }

  grouping ext-community-attributes {
    description
      "A grouping for all extended community parameters.";

    leaf-list ext-communities {
      type bct:bgp-ext-community-type;
      description
        "List of BGP extended community attributes. The received
         extended community may be an explicitly modeled
         type or unknown, represented by an 8-octet value
         formatted according to RFC 4360.";
      reference
        "RFC 4360: BGP Extended Communities Attribute.";
    }

    leaf-list ext-communities-raw {
      type string {
        // raw with 8 octets
        pattern
          'raw:([0-9A-F][0-9A-F]:){7}[0-9A-F][0-9A-F]';
      }
      description
        "ext-community type in raw format only.";
    }
  }

  grouping ipv6-ext-community-attributes {
    description
      "A grouping for all IPv6 extended community parameters.";

    leaf-list ipv6-ext-communities {
      type bct:bgp-ipv6-ext-community-type;
      description
        "List of BGP IPv6 extended community attributes. The received
         IPv6 extended community may be an explicitly modeled
         type or unknown, represented by an 20-octet value
         formatted according to RFC 5701.";
      reference
        "RFC 5701: IPv6 Address Specific BGP Extended Community
         Attribute, Section 3.";
    }

    leaf-list ipv6-ext-communities-raw {
      type string {
        // raw with 20 octets
        pattern
          'ipv6-raw:'
        + '([0-9A-Fa-f][0-9A-Fa-f]:){19}'
        + '[0-9A-Fa-f][0-9A-Fa-f]';
      }
      description
        "IPv6 ext-community type in raw format only.";
    }
  }

  grouping large-community-attributes {
    description
      "A grouping for all large community parameters.";

    leaf-list large-communities {
      type bct:bgp-large-community-type;
      description
        "List of BGP large community attributes.";
      reference
        "RFC 8092: BGP Large Communities Attribute.";
    }
  }
}
