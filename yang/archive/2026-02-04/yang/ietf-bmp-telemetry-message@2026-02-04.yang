module ietf-bmp-telemetry-message {
  yang-version 1.1;
  namespace "urn:ietf:params:xml:ns:yang:ietf-bmp-telemetry-message";
  prefix bmptm;

  import ietf-telemetry-message {
    prefix tm;
    reference
      "draft-netana-nmop-message-broker-telemetry-message: Extensible
       YANG Model for Network Telemetry Messages";
  }
  import ietf-inet-types {
    prefix inet;
    reference
      "RFC 9911: Common YANG Data Types";
  }
  import ietf-yang-types {
    prefix yang;
    reference
      "RFC 9911: Common YANG Data Types";
  }
  import ietf-routing-types {
    prefix rt-types;
    reference
      "RFC 8294: Common YANG Data Types for the Routing Area.";
  }
  import ietf-yang-structure-ext {
    prefix sx;
    reference
      "RFC 8791: YANG Data Structure Extensions";
  }
  include ietf-bmp-bgp-rib-entry {
    revision-date 2026-02-04;
  }
  include ietf-bmp-bgp-rib-tables {
    revision-date 2026-02-04;
  }
  include ietf-bmp-bgp-rib-attributes {
    revision-date 2026-02-04;
  }

  organization
    "IETF Draft";
  contact
    "Author:    Thomas Graf
                <mailto:thomas.graf@swisscom.com>
                Paolo Lucente
                <mailto:paolo@ntt.net>
                Leonardo Rodoni
                <mailto:leonardo.rodoni@swisscom.com>";

  description
    "Adds BMP specific subscription metadata to the data collection
     protocol provenance of the ietf-telemetry-message envelope.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2026 IETF Trust and the persons identified as
       authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC XXXX; see the RFC
     itself for full legal notices.";

  revision 2026-02-04 {
    description
      "Initial revision.";
    reference
      "RFC XXXX";
  }

  typedef peer-type {
    type enumeration {
      enum global-instance-peer {
        value 0;
        description
          "Global Instance Peer";
        reference
          "RFC 7854: BGP Monitoring Protocol (BMP), Section 4.2.";
      }
      enum rd-instance-peer {
        value 1;
        description
          "RD Instance Peer";
        reference
          "RFC 7854: BGP Monitoring Protocol (BMP), Section 4.2.";
      }
      enum local-instance-peer {
        value 2;
        description
          "Local Instance Peer";
        reference
          "RFC 7854: BGP Monitoring Protocol (BMP), Section 4.2.";
      }
      enum loc-rib-instance-peer {
        value 3;
        description
          "Loc-RIB Instance Peer";
        reference
          "RFC 9069: Support for Local RIB in the BGP Monitoring Protocol (BMP)";
      }
    }
    description
      "BMP Peer Type.";
    reference
      "RFC 7854: BGP Monitoring Protocol (BMP), Section 4.2.";
  }

  grouping per-peer {
    description
      "BMP per-peer header.";
    reference
      "RFC 7854: BGP Monitoring Protocol (BMP), Section 4.2.";
    leaf peer-type {
      type peer-type;
      description
        "BMP peer type from per-peer header.";
      reference
        "RFC 7854: BGP Monitoring Protocol (BMP), Section 4.2.";
    }
    leaf peer-flags {
      type uint8;
      description
        "BMP peer flags from per-peer header.";
      reference
        "RFC 7854: BGP Monitoring Protocol (BMP), Section 4.2.";
    }
    leaf peer-distinguisher {
      type rt-types:route-distinguisher;
      description
        "BMP peer distinguisher from per-peer header.";
      reference
        "RFC 7854: BGP Monitoring Protocol (BMP), Section 4.2.
         The routing instance on which the encapsulated PDU was
         received.";
    }
    leaf peer-address {
      type inet:ip-address;
      description
        "BMP peer IP address from per-peer header.";
      reference
        "RFC 7854: BGP Monitoring Protocol (BMP), Section 4.2. The
         remote IP address associated with the TCP session over which
         the encapsulated PDU was received.";
    }
    leaf peer-as {
      type uint32;
      description
        "BMP peer autonomous system number from per-peer header. The
         Autonomous System number of the peer from which the
         encapsulated PDU was received.";
      reference
        "RFC 7854: BGP Monitoring Protocol (BMP), Section 4.2.";
    }
    leaf timestamp {
      type yang:date-and-time;
      description
        "BMP timestamp from per-peer header. The time when the
         encapsulated routes were received (one may also think of this
         as the time when they were installed in the Adj-RIB-In).";
      reference
        "RFC 7854: BGP Monitoring Protocol (BMP), Section 4.2.";
    }
  }

  grouping information {
    description
      "BMP Information.";
    reference
      "RFC 7854: BGP Monitoring Protocol (BMP), Section 4.4.";
    leaf string {
      type string {
        length "1..65535";
      }
      description
        "BMP string type. The Information field contains a free-form
         UTF-8 string.";
    }
    leaf sys-descr {
      type string {
        length "1..65535";
      }
      description
        "BMP sysDescr type. The Information field contains an ASCII
         string whose value MUST be set to be equal to the value of the
         sysDescr MIB-II RFC 1213 object.";
    }
    leaf sys-name {
      type string {
        length "1..65535";
      }
      description
        "BMP sysName type. The Information field contains an ASCII
         string whose value MUST be set to be equal to the value of the
         sysName MIB-II RFC 1213 object.";
      reference
        "RFC 7854: BGP Monitoring Protocol (BMP), Section 4.2.";
    }
  }

  grouping termination {
    description
      "BMP Termination.";
    reference
      "RFC 7854: BGP Monitoring Protocol (BMP), Section 4.5.";
    leaf string {
      type string {
        length "1..65535";
      }
      description
        "BMP string type. The Information field contains a free-form
         UTF-8 string.";
    }
    leaf reason {
      type enumeration {
        enum administratively-closed {
          value 0;
        }
        enum unspecified {
          value 1;
        }
        enum out-of-resources {
          value 2;
        }
        enum redundant-connection {
          value 3;
        }
        enum permanently-administratively-closed {
          value 4;
        }
      }
    }
  }

  grouping mirroring {
    description
      "BMP Mirroring.";
    reference
      "RFC 7854: BGP Monitoring Protocol (BMP), Section 4.7.";
    leaf information {
      type enumeration {
        enum error-pdu {
          value 0;
        }
        enum message-lost {
          value 1;
        }
      }
    }
  }

  grouping statistics {
    description
      "BMP Statistics.";
    reference
      "RFC 7854: BGP Monitoring Protocol (BMP), Section 4.8.";
    leaf statistics-type {
      type string {
      }
      description
        "BMP statistics type. Defines the type of the statistic carried
         in the Stat Data field.";
    }
    leaf statistics-data {
      type uint64;
      description
        "BMP statistics data. Defines the value of the statistic.";
    }
  }

  sx:structure message {
    description
      "Augments telemetry-message-metadata with BMP specific
       subscription metadata";

    leaf version {
      type uint8;
      description
        "BMP version from common header.";
      reference
        "RFC 7854: BGP Monitoring Protocol (BMP), Section 4.1.";
    }
    choice message-type {
      description
        "BMP message type from common header.";
      reference
        "RFC 7854: BGP Monitoring Protocol (BMP), Section 4.1.";
      case route-monitoring {
        container route-monitoring {
          uses per-peer;
          uses rib-entry;
        }
      }
      case statistics-report {
        container statistics-report {
          uses per-peer;
          uses statistics;
        }
      }
      case peer-down-notification {
        container peer-down-notification {
          uses per-peer;
        }
      }
      case peer-up-notification {
        container peer-up-notification {
          uses per-peer;
        }
      }
      case initiation-message {
        container initiation-message {
          uses information;
        }
      }
      case termination-message {
        container termination-message {
          uses termination;
        }
      }
      case route-mirroring-message {
        container route-mirroring-message {
          uses per-peer;
          uses rib-entry;
          uses mirroring;
        }
      }
    }
  }
}
