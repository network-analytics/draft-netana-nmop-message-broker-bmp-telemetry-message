module ietf-bgp-open {
  yang-version 1.1;
  namespace "urn:ietf:params:xml:ns:yang:ietf-bgp-open";
  prefix bgo;

  import ietf-inet-types {
    prefix inet;
    reference
      "RFC 9911: Common YANG Data Types.";
  }

  // TODO: in the future import the single capabilities module if at idr
  // they decide to move from submodules to a modules
  import ietf-bgp {
    prefix bgp;
    reference
      "RFC XXXX: YANG Model for Border Gateway Protocol (BGP-4).";
  }

  organization
    "IETF Draft";
  contact
    "Author:    Thomas Graf
                <mailto:thomas.graf@swisscom.com>
                Paolo Lucente
                <mailto:paolo@ntt.net>
                Leonardo Rodoni
                <mailto:leonardo.rodoni@swisscom.com>
                Maxence Younsi
                <mailto:maxence.younsi4@swisscom.com>";

  description
    "Defines a grouping for representing a BGP OPEN message as
     defined in RFC 4271. The BGP OPEN message is the first
     message sent by each side after a TCP connection is
     established and carries session parameters including the
     BGP version, the sender's AS number, the Hold Time, the
     BGP Identifier, and the list of optional capabilities.
     
     This module complements the ietf-bgp model by exposing the
     OPEN message fields in a standalone reusable grouping,
     intended for use by BMP and other BGP monitoring or
     telemetry protocols.
     
     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.
     
     Copyright (c) 2026 IETF Trust and the persons identified as
     authors of the code. All rights reserved.
     
     Redistribution and use in source and binary forms, with or without
     modification, is permitted pursuant to, and subject to the license
     terms contained in, the Revised BSD License set forth in Section
     4.c of the IETF Trust's Legal Provisions Relating to IETF Documents
     (https://trustee.ietf.org/license-info).
     
     This version of this YANG module is part of RFC XXXX; see the RFC
     itself for full legal notices.";

  revision 2026-10-22 {
    description
      "Initial Version";
    reference
      "RFC XXXX";
  }

  grouping bgp-open {
    description
      "Fields from a BGP OPEN message.";
    reference
      "RFC 4271: A Border Gateway Protocol 4 (BGP-4), Section 4.2.";
    leaf version {
      type uint8;
      mandatory true;
      description
        "BGP protocol version number carried in the OPEN message.
         The current BGP version number is 4.";
      reference
        "RFC 4271: A Border Gateway Protocol 4 (BGP-4), Section 4.2.";
    }
    leaf my-as {
      type uint32;
      mandatory true;
      description
        "Autonomous System number of the BGP OPEN message sender.";
      reference
        "RFC 4271: A Border Gateway Protocol 4 (BGP-4), Section 4.2.
         RFC 6793: BGP Support for Four-Octet Autonomous System (AS)
         Number Space.";
    }
    leaf hold-time {
      type uint16;
      units "seconds";
      mandatory true;
      description
        "Hold Time proposed by the sender in the BGP OPEN message.
         The Hold Time MUST be either zero or at least three seconds.";
      reference
        "RFC 4271: A Border Gateway Protocol 4 (BGP-4), Section 4.2.";
    }
    leaf bgp-identifier {
      type inet:ipv4-address;
      mandatory true;
      description
        "BGP Identifier of the sender, set to an IP address assigned
         to that BGP speaker. The value is determined upon startup
         and is the same for every local interface and BGP peer.";
      reference
        "RFC 4271: A Border Gateway Protocol 4 (BGP-4), Section 4.2.";
    }
    // TODO: check if we can ignore/need the index?
    list capabilities {
      key "code index";
      description
        "List of BGP capabilities carried in the BGP OPEN message,
         identified by the Capability Code and an index.
         The index covers the case where the same BGP Capability
         may be advertised more than once.";
      reference
        "RFC 5492: Capabilities Advertisement with BGP-4, Section 4.";
      uses bgp:bgp-capabilities-common;
    }
  }
}
