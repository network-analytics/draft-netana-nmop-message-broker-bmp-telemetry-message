module iana-bmp-statistics-types {
  yang-version 1.1;
  namespace "urn:ietf:params:xml:ns:yang:iana-bmp-statistics-types";
  prefix bstt;

  organization
    "IETF Draft";
  contact
    "Author:    Thomas Graf
                <mailto:thomas.graf@swisscom.com>
                Paolo Lucente
                <mailto:paolo@ntt.net>
                Leonardo Rodoni
                <mailto:leonardo.rodoni@swisscom.com>
                Maxence Younsi
                <mailto:maxence.younsi@swisscom.com>";

  description
    "Defines identities mirroring the IANA 'BMP Statistics Types'
     registry, part of the 'BGP Monitoring Protocol (BMP)
     Parameters' registry group. Each identity corresponds to one
     assigned Stat Type from RFC 7854, RFC 8671, or RFC 9972.
     
     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.
     
     Copyright (c) 2026 IETF Trust and the persons identified as
       authors of the code. All rights reserved.
     
     Redistribution and use in source and binary forms, with or without
     modification, is permitted pursuant to, and subject to the license
     terms contained in, the Revised BSD License set forth in Section
     4.c of the IETF Trust's Legal Provisions Relating to IETF Documents
     (https://trustee.ietf.org/license-info).
     
     This version of this YANG module is part of RFC XXXX; see the RFC
     itself for full legal notices.";

  revision 2026-10-01 {
    description
      "Initial Version";
    reference
      "RFC XXXX";
  }

  identity bmp-stat-type {
    description
      "Base identity for BMP Statistics Types.";
    reference
      "IANA BMP Statistics Types registry; RFC 7854 Section 4.8;
       RFC 8671 Section 6.2; RFC 9972 Section 3.";
  }

  identity counter-stat-type {
    base bmp-stat-type;
    description
      "Marker identity for Stat Types whose Stat Data is a 32-bit
       counter (Stat Len = 4).";
    reference
      "RFC 7854: BGP Monitoring Protocol (BMP), Section 4.8.";
  }

  identity gauge-stat-type {
    base bmp-stat-type;
    description
      "Marker identity for Stat Types whose Stat Data is a global
       64-bit gauge (Stat Len = 8).";
    reference
      "RFC 7854: BGP Monitoring Protocol (BMP), Section 4.8.
       RFC 9972: Advanced BGP Monitoring Protocol (BMP)
       Statistics Types, Section 3.1.";
  }

  identity afi-safi-gauge-stat-type {
    base bmp-stat-type;
    description
      "Marker identity for Stat Types whose Stat Data is a 64-bit
       gauge scoped to an AFI/SAFI (2-byte AFI + 1-byte SAFI +
       64-bit gauge, Stat Len = 11).";
    reference
      "RFC 7854: BGP Monitoring Protocol (BMP), Section 4.8.
       RFC 9972: Advanced BGP Monitoring Protocol (BMP)
       Statistics Types, Section 3.1.";
  }

  identity unknown-stat-type {
    base bmp-stat-type;
    description
      "Catch-all identity for a Stat Type without a corresponding
       derived identity yet.";
    reference
      "RFC 7854: BGP Monitoring Protocol (BMP), Section 10.4.";
  }

  // RFC 7854 Section 4.8: Stat Types 0-13.
  identity prefixes-rejected-by-inbound-policy {
    base counter-stat-type;
    description
      "Stat Type 0: Number of prefixes rejected by inbound
       policy.";
    reference
      "RFC 7854: BGP Monitoring Protocol (BMP), Section 4.8.";
  }

  identity duplicate-prefix-advertisements {
    base counter-stat-type;
    description
      "Stat Type 1: Number of (known) duplicate prefix
       advertisements.";
    reference
      "RFC 7854: BGP Monitoring Protocol (BMP), Section 4.8.";
  }

  identity duplicate-withdraws {
    base counter-stat-type;
    description
      "Stat Type 2: Number of (known) duplicate withdraws.";
    reference
      "RFC 7854: BGP Monitoring Protocol (BMP), Section 4.8.";
  }

  identity updates-invalidated-due-to-cluster-list-loop {
    base counter-stat-type;
    description
      "Stat Type 3: Number of updates invalidated due to
       CLUSTER_LIST loop.";
    reference
      "RFC 7854: BGP Monitoring Protocol (BMP), Section 4.8.";
  }

  identity updates-invalidated-due-to-as-path-loop {
    base counter-stat-type;
    description
      "Stat Type 4: Number of updates invalidated due to AS_PATH
       loop.";
    reference
      "RFC 7854: BGP Monitoring Protocol (BMP), Section 4.8.";
  }

  identity updates-invalidated-due-to-originator-id {
    base counter-stat-type;
    description
      "Stat Type 5: Number of updates invalidated due to
       ORIGINATOR_ID.";
    reference
      "RFC 7854: BGP Monitoring Protocol (BMP), Section 4.8.";
  }

  identity updates-invalidated-due-to-as-confed-loop {
    base counter-stat-type;
    description
      "Stat Type 6: Number of updates invalidated due to a loop
       found in AS_CONFED_SEQUENCE or AS_CONFED_SET.";
    reference
      "RFC 7854: BGP Monitoring Protocol (BMP), Section 4.8.";
  }

  identity routes-in-adj-rib-in {
    base gauge-stat-type;
    description
      "Stat Type 7: Number of routes in Adj-RIBs-In.";
    reference
      "RFC 7854: BGP Monitoring Protocol (BMP), Section 4.8.";
  }

  identity routes-in-loc-rib {
    base gauge-stat-type;
    description
      "Stat Type 8: Number of routes in Loc-RIB.";
    reference
      "RFC 7854: BGP Monitoring Protocol (BMP), Section 4.8.";
  }

  identity routes-in-per-afi-safi-adj-rib-in {
    base afi-safi-gauge-stat-type;
    description
      "Stat Type 9: Number of routes in per-AFI/SAFI
       Adj-RIB-In.";
    reference
      "RFC 7854: BGP Monitoring Protocol (BMP), Section 4.8.";
  }

  identity routes-in-per-afi-safi-loc-rib {
    base afi-safi-gauge-stat-type;
    description
      "Stat Type 10: Number of routes in per-AFI/SAFI Loc-RIB.";
    reference
      "RFC 7854: BGP Monitoring Protocol (BMP), Section 4.8.";
  }

  identity updates-subjected-to-treat-as-withdraw {
    base counter-stat-type;
    description
      "Stat Type 11: Number of updates subjected to
       treat-as-withdraw.";
    reference
      "RFC 7854: BGP Monitoring Protocol (BMP), Section 4.8.";
  }

  identity prefixes-subjected-to-treat-as-withdraw {
    base counter-stat-type;
    description
      "Stat Type 12: Number of prefixes subjected to
       treat-as-withdraw.";
    reference
      "RFC 7854: BGP Monitoring Protocol (BMP), Section 4.8.";
  }

  identity duplicate-update-messages-received {
    base counter-stat-type;
    description
      "Stat Type 13: Number of duplicate update messages
       received.";
    reference
      "RFC 7854: BGP Monitoring Protocol (BMP), Section 4.8.";
  }

  // RFC 8671 Section 6.2: Stat Types 14-17.
  identity routes-in-pre-policy-adj-rib-out {
    base gauge-stat-type;
    description
      "Stat Type 14: Number of routes in pre-policy
       Adj-RIB-Out.";
    reference
      "RFC 8671: Support for Adj-RIB-Out in the BGP Monitoring
       Protocol (BMP), Section 6.2.";
  }

  identity routes-in-post-policy-adj-rib-out {
    base gauge-stat-type;
    description
      "Stat Type 15: Number of routes in post-policy
       Adj-RIB-Out.";
    reference
      "RFC 8671: Support for Adj-RIB-Out in the BGP Monitoring
       Protocol (BMP), Section 6.2.";
  }

  identity routes-in-per-afi-safi-pre-policy-adj-rib-out {
    base afi-safi-gauge-stat-type;
    description
      "Stat Type 16: Number of routes in per-AFI/SAFI pre-policy
       Adj-RIB-Out.";
    reference
      "RFC 8671: Support for Adj-RIB-Out in the BGP Monitoring
       Protocol (BMP), Section 6.2.";
  }

  identity routes-in-per-afi-safi-post-policy-adj-rib-out {
    base afi-safi-gauge-stat-type;
    description
      "Stat Type 17: Number of routes in per-AFI/SAFI
       post-policy Adj-RIB-Out.";
    reference
      "RFC 8671: Support for Adj-RIB-Out in the BGP Monitoring
       Protocol (BMP), Section 6.2.";
  }

  // RFC 9972 Section 3: Stat Types 18-23, 26-43.
  // Stat Types 24-25 (primary/backup route) are intentionally
  // not modeled here: they were only temporarily registered and
  // expiring on 2026-10-18, and were dropped from the final
  // RFC 9972 text; if needed use unknown-stat-type statistics-type.
  identity routes-in-pre-policy-adj-rib-in {
    base gauge-stat-type;
    description
      "Stat Type 18: Number of routes currently in the
       pre-policy Adj-RIB-In.";
    reference
      "RFC 9972: Advanced BGP Monitoring Protocol (BMP)
       Statistics Types, Section 3.2.";
  }

  identity routes-in-per-afi-safi-pre-policy-adj-rib-in {
    base afi-safi-gauge-stat-type;
    description
      "Stat Type 19: Number of routes currently in the
       per-AFI/SAFI pre-policy Adj-RIB-In.";
    reference
      "RFC 9972: Advanced BGP Monitoring Protocol (BMP)
       Statistics Types, Section 3.2.";
  }

  identity routes-in-post-policy-adj-rib-in {
    base gauge-stat-type;
    description
      "Stat Type 20: Number of routes currently in the
       post-policy Adj-RIB-In.";
    reference
      "RFC 9972: Advanced BGP Monitoring Protocol (BMP)
       Statistics Types, Section 3.2.";
  }

  identity routes-in-per-afi-safi-post-policy-adj-rib-in {
    base afi-safi-gauge-stat-type;
    description
      "Stat Type 21: Number of routes currently in the
       per-AFI/SAFI post-policy Adj-RIB-In.";
    reference
      "RFC 9972: Advanced BGP Monitoring Protocol (BMP)
       Statistics Types, Section 3.2.";
  }

  identity routes-in-per-afi-safi-pre-policy-adj-rib-in-rejected {
    base afi-safi-gauge-stat-type;
    description
      "Stat Type 22: Number of routes currently in the
       per-AFI/SAFI pre-policy Adj-RIB-In rejected by an inbound
       policy.";
    reference
      "RFC 9972: Advanced BGP Monitoring Protocol (BMP)
       Statistics Types, Section 3.2.";
  }

  identity routes-in-per-afi-safi-post-policy-adj-rib-in-accepted {
    base afi-safi-gauge-stat-type;
    description
      "Stat Type 23: Number of routes currently in the
       per-AFI/SAFI post-policy Adj-RIB-In accepted by an
       inbound policy.";
    reference
      "RFC 9972: Advanced BGP Monitoring Protocol (BMP)
       Statistics Types, Section 3.2.";
  }

  identity routes-suppressed-by-route-damping {
    base afi-safi-gauge-stat-type;
    description
      "Stat Type 26: Number of routes currently in the
       per-AFI/SAFI post-policy Adj-RIB-In or Loc-RIB suppressed
       by a configured route-damping policy.";
    reference
      "RFC 9972: Advanced BGP Monitoring Protocol (BMP)
       Statistics Types, Section 3.2.";
  }

  identity routes-marked-stale-by-gr {
    base afi-safi-gauge-stat-type;
    description
      "Stat Type 27: Number of routes currently in the
       per-AFI/SAFI post-policy Adj-RIB-In or Loc-RIB marked as
       stale by Graceful Restart (GR) events.";
    reference
      "RFC 9972: Advanced BGP Monitoring Protocol (BMP)
       Statistics Types, Section 3.2.";
  }

  identity routes-marked-stale-by-llgr {
    base afi-safi-gauge-stat-type;
    description
      "Stat Type 28: Number of routes currently in the
       per-AFI/SAFI post-policy Adj-RIB-In or Loc-RIB marked as
       stale by Long-Lived Graceful Restart (LLGR).";
    reference
      "RFC 9972: Advanced BGP Monitoring Protocol (BMP)
       Statistics Types, Section 3.2.";
  }

  identity routes-left-before-received-route-threshold {
    base gauge-stat-type;
    description
      "Stat Type 29: Number of routes currently in the
       post-policy Adj-RIB-In left before exceeding the
       received-route threshold.";
    reference
      "RFC 9972: Advanced BGP Monitoring Protocol (BMP)
       Statistics Types, Section 3.2.";
  }

  identity routes-in-per-afi-safi-left-before-received-route-threshold {
    base afi-safi-gauge-stat-type;
    description
      "Stat Type 30: Number of routes currently in the
       per-AFI/SAFI post-policy Adj-RIB-In left before exceeding
       the received-route threshold.";
    reference
      "RFC 9972: Advanced BGP Monitoring Protocol (BMP)
       Statistics Types, Section 3.2.";
  }

  identity routes-left-before-license-route-threshold {
    base gauge-stat-type;
    description
      "Stat Type 31: Number of routes currently in the
       post-policy Adj-RIB-In or Loc-RIB left before exceeding a
       license-customized route threshold.";
    reference
      "RFC 9972: Advanced BGP Monitoring Protocol (BMP)
       Statistics Types, Section 3.2.";
  }

  identity routes-in-per-afi-safi-left-before-license-route-threshold {
    base afi-safi-gauge-stat-type;
    description
      "Stat Type 32: Number of routes currently in the
       per-AFI/SAFI post-policy Adj-RIB-In or Loc-RIB left
       before exceeding a license-customized route threshold.";
    reference
      "RFC 9972: Advanced BGP Monitoring Protocol (BMP)
       Statistics Types, Section 3.2.";
  }

  identity routes-rejected-due-to-as-path-length {
    base gauge-stat-type;
    description
      "Stat Type 33: Number of routes currently in the
       pre-policy Adj-RIB-In rejected due to exceeding the
       locally configured maximum AS_PATH length.";
    reference
      "RFC 9972: Advanced BGP Monitoring Protocol (BMP)
       Statistics Types, Section 3.2.";
  }

  identity routes-in-per-afi-safi-rejected-due-to-as-path-length {
    base afi-safi-gauge-stat-type;
    description
      "Stat Type 34: Number of routes currently in the
       per-AFI/SAFI pre-policy Adj-RIB-In rejected due to
       exceeding the locally configured maximum AS_PATH
       length.";
    reference
      "RFC 9972: Advanced BGP Monitoring Protocol (BMP)
       Statistics Types, Section 3.2.";
  }

  identity routes-in-per-afi-safi-invalidated-by-rpki {
    base afi-safi-gauge-stat-type;
    description
      "Stat Type 35: Number of routes currently in the
       per-AFI/SAFI post-policy Adj-RIB-In invalidated after
       verifying the route origin AS number through the ROA of
       the RPKI, due to a mismatch of origin ASN and/or prefix
       length.";
    reference
      "RFC 9972: Advanced BGP Monitoring Protocol (BMP)
       Statistics Types, Section 3.2.
       RFC 6811: BGP Prefix Origin Validation.";
  }

  identity routes-in-per-afi-safi-validated-by-rpki {
    base afi-safi-gauge-stat-type;
    description
      "Stat Type 36: Number of routes currently in the
       per-AFI/SAFI post-policy Adj-RIB-In validated after
       verifying the route origin AS number through the ROA of
       the RPKI.";
    reference
      "RFC 9972: Advanced BGP Monitoring Protocol (BMP)
       Statistics Types, Section 3.2.
       RFC 6811: BGP Prefix Origin Validation.";
  }

  identity routes-in-per-afi-safi-rpki-not-found {
    base afi-safi-gauge-stat-type;
    description
      "Stat Type 37: Number of routes currently in the
       per-AFI/SAFI post-policy Adj-RIB-In whose RPKI route
       origin validation state is NotFound due to the absence of
       a matching ROA of the RPKI.";
    reference
      "RFC 9972: Advanced BGP Monitoring Protocol (BMP)
       Statistics Types, Section 3.2.
       RFC 6811: BGP Prefix Origin Validation.";
  }

  identity routes-in-per-afi-safi-pre-policy-adj-rib-out-rejected {
    base afi-safi-gauge-stat-type;
    description
      "Stat Type 38: Number of routes currently in the
       per-AFI/SAFI pre-policy Adj-RIB-Out rejected by an
       outbound policy.";
    reference
      "RFC 9972: Advanced BGP Monitoring Protocol (BMP)
       Statistics Types, Section 3.3.";
  }

  identity routes-in-pre-policy-adj-rib-out-filtered-due-to-as-path-length {
    base gauge-stat-type;
    description
      "Stat Type 39: Number of routes currently in the
       pre-policy Adj-RIB-Out filtered due to AS_PATH length
       exceeding the locally configured maximum.";
    reference
      "RFC 9972: Advanced BGP Monitoring Protocol (BMP)
       Statistics Types, Section 3.3.";
  }

  identity routes-in-per-afi-safi-pre-policy-adj-rib-out-filtered-due-to-as-path-length {
    base afi-safi-gauge-stat-type;
    description
      "Stat Type 40: Number of routes currently in the
       per-AFI/SAFI pre-policy Adj-RIB-Out filtered due to
       AS_PATH length exceeding the locally configured
       maximum.";
    reference
      "RFC 9972: Advanced BGP Monitoring Protocol (BMP)
       Statistics Types, Section 3.3.";
  }

  identity routes-in-per-afi-safi-post-policy-adj-rib-out-invalidated-by-rpki {
    base afi-safi-gauge-stat-type;
    description
      "Stat Type 41: Number of routes currently in the
       per-AFI/SAFI post-policy Adj-RIB-Out invalidated after
       verifying the route origin AS number through the ROA of
       the RPKI, due to a mismatch of origin ASN and/or prefix
       length.";
    reference
      "RFC 9972: Advanced BGP Monitoring Protocol (BMP)
       Statistics Types, Section 3.3.
       RFC 6811: BGP Prefix Origin Validation.";
  }

  identity routes-in-per-afi-safi-post-policy-adj-rib-out-validated-by-rpki {
    base afi-safi-gauge-stat-type;
    description
      "Stat Type 42: Number of routes currently in the
       per-AFI/SAFI post-policy Adj-RIB-Out validated after
       verifying the route origin AS number through the ROA of
       the RPKI.";
    reference
      "RFC 9972: Advanced BGP Monitoring Protocol (BMP)
       Statistics Types, Section 3.3.
       RFC 6811: BGP Prefix Origin Validation.";
  }

  identity routes-in-per-afi-safi-post-policy-adj-rib-out-rpki-not-found {
    base afi-safi-gauge-stat-type;
    description
      "Stat Type 43: Number of routes currently in the
       per-AFI/SAFI post-policy Adj-RIB-Out whose RPKI route
       origin validation state is NotFound due to the absence of
       a matching ROA of the RPKI.";
    reference
      "RFC 9972: Advanced BGP Monitoring Protocol (BMP)
       Statistics Types, Section 3.3.
       RFC 6811: BGP Prefix Origin Validation.";
  }
}
